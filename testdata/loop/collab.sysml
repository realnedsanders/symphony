package SymphonyCollab {
    part propIngest {
        attribute recordKind = "proposal";
        attribute gap = "gapIngest";
        attribute branch = "proposal/gapIngest";
        attribute worktree = "";
        attribute phase = "open";
        attribute touch_0 = "ingest.input";
    }
}
